FME workspace Trajectory2.fmw

Parameters:
- userdetails =   # User Details
- firstname = First
- lastname = Last
- emailaddress = Email@email.com
- PARAMETER_5 =   # Role
- relationship = other
- dicipline = civil   # Dicipline
- project =   # Project
- projectname = myproject   # Project Name
- projectnumber = 000000000.00   # Project Number
- batch = <Unused>   # Batch Add Users from File
- batchyes_no = NO   # Batch (Ignore User Entry)
- file =
- DestDataset_SQLITE3 = B:\Git\trajectory2\TestData\SQliteSamples\TestProject.sqlite   # SQLite Database

Writers:
- SQLITE3_1: SQLITE3 to $(DestDataset_SQLITE3)

Creator
    GEOMTYPE = Geometry Object
    NUM = 1
    CREATED -> AttributeManager
AttributeManager
    ATTR_TABLE:
      SET_TO datetime = @DateTimeNow()
      SET_TO transactionguid = @UUID()
    -> AttributeFilter
AttributeFilter
    ATTR_NAME = $(batchyes_no)
    ATTR_VALUES = <Missing>,yes,<Empty>,<Null>,<Unfiltered>
    <MISSING> -> Transaction_Add_User (writer SQLITE3_1)
Transaction_Add_User (writer SQLITE3_1)
    attributes: transactionID varchar(200), datetime varchar(200), userfirst varchar(200), userlast varchar(200), useremail varchar(200), userelationship varchar(200), userdicipline varchar(200), projectname varchar(200), projectnumber varchar(200)
